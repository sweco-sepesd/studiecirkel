FME workspace FetchRecords.fmw

Parameters:
- Filter = artist@Depeche Mode;format@Vinyl
- Token =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   # Enter a Password
- Artist = Kraftwerk
- Album = Trans Europa Express
- Format =

Creator_2
    GEOMTYPE = Geometry Object
    NUM = 1
    CREATED -> HTTPCaller
Note: Get all records from Discogs
HTTPCaller
    ADDITIONAL_URL_PARAMETERS = Authorization;bearer $(Token) sort;artist
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.discogs.com/users/Hazzelman/collection/folders/0/releases?page=1&per_page=300
    TRANSFER_TIMEOUT_LENGTH = 90
    USE_COOKIES = No
    VERIFY_SSL_CERTIFICATES = Yes
    -> ParameterFetcher
Note: Fetch parameters
ParameterFetcher
    ATTR_LIST = _Filter $(Filter) _Artist $(Artist) _Album $(Album) _Format $(Format)
    -> AttributeCreator_2
AttributeCreator_2
    ATTR_TABLE = SET_TO _Filter (buffer) = FME_CONDITIONAL:DEFAULT_VALUE'FME_NULL_VALUE'BOOL_OP;AND;COMPOSITE_TEST;1 AND 2;TEST _Artist ATTRIBUTE_HAS_A_VALUE _FME_BLANK_STRING_;TEST _Format ATTRIBUTE_HAS_A_VALUE _FME_BLANK_STRING_'artist@@Value(_Artist);format@@Value(_Format)'BOOL_OP;AND;COMPOSITE_TEST;1 AND 2;TEST _Artist ATTRIBUTE_HAS_A_VALUE _FME_BLANK_STRING_;TEST _Format NOT_ATTRIBUTE_HAS_A_VALUE _FME_BLANK_STRING_'artist@@Value(_Artist)'BOOL_OP;AND;COMPOSITE_TEST;1 AND 2;TEST _Artist ATTRIBUTE_HAS_A_VALUE _FME_BLANK_STRING_;TEST _Format ATTRIBUTE_HAS_A_VALUE _FME_BLANK_STRING_'format@@Value(_Format)'FME_NUM_CONDITIONS4___
    -> StringConcatenator
Note: Concatenate filter parameters into known string
StringConcatenator
    ACTION = Create New Attribute
    PARM_LINE = fme_basicstring:7%15%7%14%8%15:artist@@Value(_Artist);album@@Value(_Album);format@@Value(_Format)
    VAL_ATTR = _Filter
    -> JSONFragmenter
JSONFragmenter
    EXPLODE_FORMAT = JSON
    EXTRACT_ATTR = Yes
    JSON_ATTR = _response_body
    JSON_QUERY = json["releases"][*]
    READ_FROM_FILE = NO
    RECURSIVE = YES
    REJECT_EMPTY_LISTS = YES
    FRAGMENTS -> AttributeExposer
AttributeExposer
    ATTR_TABLE = basic_information.id,,basic_information.master_id,,basic_information.master_url,,basic_information.resource_url,,basic_information.cover_image,,basic_information.title,,basic_information.year,,date_added,,rating,,basic_information.artists{}.name,,basic_information.artists{}.resource_url,,basic_information.artists{}.id,,basic_information.formats{}.descriptions{},,basic_information.formats{}.name,,basic_information.formats{}.gty,,basic_information.formats{}.text,,basic_information.genres{},,basic_information.labels{}.catno,,basic_information.labels{}.entity_type_name,,basic_information.labels{}.id,,basic_information.labels{}.name,,basic_information.labels{}.resource_url,,basic_information.styles{},,basic_information.*,
    -> PythonCaller_2
Note: Filter records according to dynamic filter and print to log
PythonCaller_2
    NEW_ATTRIBUTES = filtered_attributes buffer
    PYTHONSOURCE:
      import fme
      import fmeobjects
      from fmeobjects import FMEFeature, FMELogFile


      class FeatureProcessor(object):
          def __init__(self):
              self.results = []
              self.attributes_list = []
              self.filter = []

          def input(self, feature: fmeobjects.FMEFeature):
              album = feature.getAttribute('basic_information.title').replace(',','_')
              year = feature.getAttribute('basic_information.year')
              artist = feature.getAttribute('basic_information.artists{0}.name')
              format = feature.getAttribute('basic_information.formats{0}.name')
              rating = feature.getAttribute('rating')
              formatDetails = str(feature.getAttribute('basic_information.formats{0}.descriptions{0}'))
              #formatDetails = '; '.join([str(s) for s in formatDetails])
              self.results.append(album)
              self.results.append(artist)

              filter = feature.getAttribute('_Filter')
              dicts = filter.split(';')
              #print(dicts)
              delim = "@"
              filter_dict = dict()
              for sub in dicts:
                  filter_dict[sub.split(delim)[0]] = sub.split(delim)[1]

              filter_dict = {k: v for k, v in filter_dict.items() if v}
              self.filter = filter_dict
              #feature.setPublishedAttribute('exposed_album', album)

              # Create a dictionary to store artist and album
              attributes_dict = {}
              attributes_dict['artist'] = feature.getAttribute('basic_information.artists{0}.name')
              attributes_dict['album'] = feature.getAttribute('basic_information.title')
              attributes_dict['format'] = feature.getAttribute('basic_information.formats{0}.name')
              attributes_dict['rating'] = feature.getAttribute('rating')
              attributes_dict['year'] = feature.getAttribute('year')
              attributes_dict['formatDetails'] = feature.getAttribute('basic_information.formats{0}.descriptions{}')

              for (key, value) in attributes_dict.items():
                  if (attributes_dict.get('artist') == filter_dict.get('artist')):
                      #print(attributes_dict['artist'] + ': ' + attributes_dict['album'] + '(' + attributes_dict['format'] +')')
                      #print(sorted(attributes_dict.items(), key=item[1]["artist"].get('Skinny Puppy'), reverse=True))
                      pass

              feature.setAttribute('Album', album)
              feature.setAttribute('Artist', artist)
              feature.setAttribute('Rating', rating)
              feature.setAttribute('Year', year)
              feature.setAttribute('filter', str(filter_dict))
              #self.pyoutput(feature)

              #fmeobjects.FMEFeature().setPublishedAttribute('album', album)

              # Append attributes to list as a dictionary
              self.attributes_list.append({'artist': artist, 'album': album, 'year': year, 'rating': rating, 'format': format, 'formatDetails': formatDetails})

          def close(self):

              filter_dict = self.filter
              sorted_attributes = sorted(self.attributes_list, key=lambda x: x['artist'])
              #print(str(sorted_attributes))
              filtered_attributes = []

              if filter_dict:
                  #print(str(filter_dict))
                  for attr in sorted_attributes:
                      #print(str(filter_dict))
                      if all(filter_dict[k] == attr.get(k, None) for k in filter_dict):
                          #print(str(attr))
                          #print(str(filter_dict))
                          filtered_attributes.append(attr)
              else:
                  filtered_attributes = sorted_attributes

              for attr in filtered_attributes:
                     print(f"{attr['artist']}: {attr['album']} ({attr['year']}) ({attr['format']}, ({attr['rating']}, {attr['formatDetails']})")
              #print(str(filtered_attributes))
              print('--------------------------------------------------------------')
              print('Totalt ' + str(len(filtered_attributes)) + ' skivor skrevs ut')
              print('--------------------------------------------------------------')


              import operator, functools

              get_value = operator.itemgetter('artist', 'album', 'rating', 'year', 'format', 'formatDetails')
              list_of_values = functools.partial(map, get_value)
              print('list of values:')
              #print(list(list_of_values(filtered_attributes)))

              # Create a new FME feature to hold the result
              result_feature = fmeobjects.FMEFeature()
              result_list = ()
              result_list = list(list_of_values(filtered_attributes))
              print(len(result_list))
              FMELogFile().logMessageString(repr(result_list))
              for i in range(0, len(result_list)-1):
                  if i==0:
                      #result_feature[i] = result_list[i]
                      pass
              result_feature.setAttribute('filtered_attributes', repr(result_list))
              self.pyoutput(result_feature)
    PYTHONSYMBOL = FeatureProcessor
    -> AttributeKeeper
AttributeKeeper
    CREATE_BULK_MODE_FEATURES = NO
    KEEP_ATTRS = filtered_attributes
    -> StringPairReplacer
StringPairReplacer
    CASE = no
    MAP = "), " ; [ "" ] "" ( "" ) "" ' "" \" ""
    SRC_ATTRS = filtered_attributes
    -> AttributeSplitter
AttributeSplitter
    ATTR_NAME = filtered_attributes
    DELIMITER = ;
    DROP_EMPTY_PARTS = NO
    LIST_NAME = _list
    TRIM_TYPE = BOTH
    -> ListExploder
ListExploder
    ATTR_ACCUM_MODE = Merge List Attributes
    ATTR_CONFLICT_RES_LOOKUP = INCOMING_IF_CONFLICT
    INDEX_ATTR = _element_index
    LIST_ATTR = _list{}
    ATTR_CONFLICT_RES = Use List Attribute Values
    ELEMENTS -> AttributeSplitter_2
AttributeSplitter_2
    ATTR_NAME = _list
    DELIMITER = ,
    DROP_EMPTY_PARTS = NO
    LIST_NAME = _list
    TRIM_TYPE = BOTH
    -> AttributeCreator
AttributeCreator
    ATTR_TABLE:
      SET_TO Artist (varchar(200)) = @Value(_list{0})
      SET_TO Album (varchar(200)) = @Value(_list{1})
      SET_TO Format (varchar(200)) = FME_CONDITIONAL:DEFAULT_VALUE'@Value(_list{3}) (@Value(_list{4}))'BOOL_OP;OR;COMPOSITE_TEST;1;TEST @Value(_list{4}) IN 7,12'@Value(_list{3}) (@Value(_list{4})")'FME_NUM_CONDITIONS2___
      SET_TO Rating (varchar(200)) = @Value(_list{2})
    -> Tester
Tester
    BOOL_OP = OR
    TEST_CLAUSE = TEST @Value(Rating) = 5
    TEST_MODE = TEST
    PASSED -> AttributeCreator_3
    FAILED -> AttributeCreator_3
AttributeCreator_3
    ATTR_TABLE = SET_TO text_line_data (varchar(200)) = @Value(Artist) - @Value(Album) (@Value(Format))
    -> Sampler
Sampler
    MODE = RANDOM
    RATE = 5
    SAMPLE_TYPE_MULTIPLIER = -1
    SAMPLE_MODE = Yes
    SAMPLE_TYPE_LONG = First N Features
    SAMPLED -> FeatureWriter [text_line]
FeatureWriter
    DATASET = Records.txt
    DATASET_ATTR = _dataset
    FEATURE_TYPE_LIST_ATTR = _feature_types
    FORMAT = TEXTLINE
    TEXTLINE_COORDINATE_SYSTEM_GRANULARITY = FEATURE
    TEXTLINE_DESTINATION_DATASETTYPE_VALIDATION = Yes
    TEXTLINE_ENCODING = iso-8859-1
    TEXTLINE_END_OF_LINE = System
    TEXTLINE_MIME_TYPE = text/plain
    TEXTLINE_OVERWRITE_FILE = YES
    TEXTLINE_WRITE_LAST_EOL = YES
    TEXTLINE_WRITE_UTF8_BOM = NO
    TOTAL_FEATURES_WRITTEN_ATTR = _total_features_written
